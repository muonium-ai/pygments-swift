module fibonacci {
  namespace "urn:example:fibonacci";
  prefix fib;

  container config {
    leaf n {
      type uint32;
      description "Input value";
    }

    leaf note {
      type string;
      description "End of fibonacci sample";
    }
  }
}

// End of fibonacci sample.
// End of fibonacci sample line 2.
// End of fibonacci sample line 3.
// End of fibonacci sample line 4.
// End of fibonacci sample line 5.
// End of fibonacci sample line 6.
